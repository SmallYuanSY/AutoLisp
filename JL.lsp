(defun c:JL ( / dir )
  (initget "X Y")
  (setq dir (getkword "\n請選擇對齊方向 [X/Y] <Y>: "))
  (command "._UNDO" "_Group")
  (if (or (not dir) (= dir "Y"))
    (c:JOINPAIR-Y)
    (c:JOINPAIR-X)
  )
  (command "._UNDO" "_End")
)

(defun c:JOINPAIR-X ( / tol sel1 sel2 i j e1 e2 y1 y2 y-map pair-list)
  (vl-load-com)
  (setq tol 1e-6)
  (prompt "\n[JOINPAIR-X] 依 X 座標對齊，配對 JOIN 兩組線段。")
  (setq sel1 (ssget '((0 . "LINE,LWPOLYLINE"))))
  (setq sel2 (ssget '((0 . "LINE,LWPOLYLINE"))))
  (setq y-map '())
  (setq i 0)
  (if sel1
    (repeat (sslength sel1)
      (setq e1 (ssname sel1 i))
      (setq y1 (cadr (vlax-curve-getstartpoint e1)))
      (setq y-map (cons (list y1 e1) y-map))
      (setq i (1+ i))
    )
  )
  (setq pair-list '())
  (setq j 0)
  (if sel2
    (repeat (sslength sel2)
      (setq e2 (ssname sel2 j))
      (setq y2 (cadr (vlax-curve-getstartpoint e2)))
      (foreach pair y-map
        (if (< (abs (- y2 (car pair))) tol)
          (setq pair-list (cons (list (cadr pair) e2) pair-list))
        )
      )
      (setq j (1+ j))
    )
  )
  (foreach p pair-list
    (command "_.JOIN" (car p) (cadr p) "")
  )
  (prompt (strcat "\n✅ JOINPAIR-Y 成功 JOIN " (itoa (length pair-list)) " 組線段。"))
  (princ)
)

(defun c:JOINPAIR-Y ( / tol sel1 sel2 i j e1 e2 x1 x2 x-map pair-list)
  (vl-load-com)
  (setq tol 1e-6)
  (prompt "\n[JOINPAIR-Y] 依 Y 座標對齊，配對 JOIN 兩組線段。")
  (setq sel1 (ssget '((0 . "LINE,LWPOLYLINE"))))
  (setq sel2 (ssget '((0 . "LINE,LWPOLYLINE"))))
  (setq x-map '())
  (setq i 0)
  (if sel1
    (repeat (sslength sel1)
      (setq e1 (ssname sel1 i))
      (setq x1 (car (vlax-curve-getstartpoint e1)))
      (setq x-map (cons (list x1 e1) x-map))
      (setq i (1+ i))
    )
  )
  (setq pair-list '())
  (setq j 0)
  (if sel2
    (repeat (sslength sel2)
      (setq e2 (ssname sel2 j))
      (setq x2 (car (vlax-curve-getstartpoint e2)))
      (foreach pair x-map
        (if (< (abs (- x2 (car pair))) tol)
          (setq pair-list (cons (list (cadr pair) e2) pair-list))
        )
      )
      (setq j (1+ j))
    )
  )
  (foreach p pair-list
    (command "_.JOIN" (car p) (cadr p) "")
  )
  (prompt (strcat "\n✅ JOINPAIR-Y 成功 JOIN " (itoa (length pair-list)) " 組線段。"))
)
