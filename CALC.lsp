(defun c:CalcFromText (/ ent txt expr result)
  (while (setq ent (car (entsel "\n請選取包含數學表達式的文字 (按Enter結束): ")))
    (cond
      ((/= (cdr (assoc 0 (entget ent))) "TEXT")
        (princ "\n選取的物件不是文字，請重新選取!")
      )
      (t
        (setq txt (cdr (assoc 1 (entget ent))))
        (if (setq expr (ParseMathExpression txt))
          (progn
            (setq result (EvaluateMathExpression expr))
            (princ (strcat "\n文字內容: " txt))
            (princ (strcat "\n提取的表達式: " expr))
            (princ (strcat "\n計算結果: " (rtos result 2 4)))
          )
          (princ "\n未找到有效的數學表達式!")
        )
      )
    )
  )
  (princ)
)

(defun ParseMathExpression (str / start end)
  (if (vl-string-search "(" str)
    (progn
      (setq start (vl-string-position (ascii "(") str))
      (setq end (vl-string-position (ascii ")") str t))
      (if (and start end (> end start))
        (substr str (+ start 2) (- end start 1))
        str
      )
    )
    str
  )
)

(defun EvaluateMathExpression (expr / tokens)
  (if (setq tokens (TokenizeExpression expr))
    (ShuntingYard tokens)
    0.0
  )
)

(defun TokenizeExpression (expr / tokens i char token len)
  (setq tokens '())
  (setq i 1)
  (setq len (strlen expr))
  (while (<= i len)
    (setq char (substr expr i 1))
    (cond
      ((or (<= (ascii "0") (ascii char) (ascii "9")) (equal char "."))
        (setq token "")
        (while (and (<= i len)
                   (or (<= (ascii "0") (ascii (setq char (substr expr i 1))) (ascii "9"))
                       (equal char ".")))
          (setq token (strcat token char))
          (setq i (1+ i))
        )
        (if (> (strlen token) 0)
          (setq tokens (append tokens (list (atof token))))
        )
      )
      ((or (equal char "+") (equal char "-") (equal char "x") (equal char "/") 
           (equal char "(") (equal char ")"))
        (setq tokens (append tokens (list char)))
        (setq i (1+ i))
      )
      ((equal char " ")
        (setq i (1+ i))
      )
      (t (setq i (1+ i)))
    )
  )
  (if tokens tokens nil)
)

(defun ShuntingYard (tokens / output opStack token)
  (setq output '())
  (setq opStack '())
  (foreach token tokens
    (cond
      ((numberp token) (setq output (cons token output)))
      ((equal token "(") (setq opStack (cons token opStack)))
      ((equal token ")")
        (while (and opStack (not (equal (car opStack) "(")))
          (setq output (cons (car opStack) output))
          (setq opStack (cdr opStack))
        )
        (if (equal (car opStack) "(")
          (setq opStack (cdr opStack))
          (princ "\n警告: 不匹配的括弧!")
        )
      )
      (t
        (while (and opStack
                    (not (equal (car opStack) "("))
                    (>= (GetPrecedence (car opStack)) (GetPrecedence token)))
          (setq output (cons (car opStack) output))
          (setq opStack (cdr opStack))
        )
        (setq opStack (cons token opStack))
      )
    )
  )
  (foreach op (reverse opStack)
    (setq output (cons op output))
  )
  (EvaluateRPN (reverse output))
)

(defun GetPrecedence (op)
  (cond
    ((or (equal op "x") (equal op "/")) 2)
    ((or (equal op "+") (equal op "-")) 1)
    (t 0)
  )
)

(defun EvaluateRPN (rpn / stack token a b)
  (setq stack '())
  (foreach token rpn
    (if (numberp token)
      (setq stack (cons token stack))
      (progn
        (if (< (length stack) 2)
          (progn
            (princ "\n錯誤: 無效的運算式!")
            (setq stack '(0.0))
            (exit)
          )
        )
        (setq b (car stack))
        (setq stack (cdr stack))
        (setq a (car stack))
        (setq stack (cdr stack))
        (setq stack
          (cons
            (cond
              ((equal token "+") (+ a b))
              ((equal token "-") (- a b))
              ((equal token "x") (* a b))
              ((equal token "/") 
                (if (zerop b) 
                  (progn 
                    (princ "\n警告: 除數為零!")
                    0.0
                  )
                  (/ a b)
                )
              )
            )
            stack
          )
        )
      )
    )
  )
  (if stack (car stack) 0.0)
)

(princ "\n文字計算器已載入，輸入 CalcFromText 開始使用。")
(princ)
