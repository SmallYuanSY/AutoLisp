(defun c:GXO ( / ent blk minPt maxPt)
  (vl-load-com)
  (setq ent (car (entsel "\n請選取一個外部參考：")))
  (if (and ent (= (cdr (assoc 0 (entget ent))) "INSERT"))
    (progn
      (setq blk (vlax-ename->vla-object ent))
      (vla-GetBoundingBox blk 'minPt 'maxPt)
      (setq minPt (vlax-safearray->list minPt))
      (setq maxPt (vlax-safearray->list maxPt))
      (princ (strcat "\n最小點: " (rtos (car minPt) 2 2) ", " (rtos (cadr minPt) 2 2)))
      (princ (strcat "\n最大點: " (rtos (car maxPt) 2 2) ", " (rtos (cadr maxPt) 2 2)))
    )
    (princ "\n請選取一個有效的外部參考。")
  )
  (princ)
)
